-- *****************************************************************
-- STAMP-SUITE-MIB: MIB for the stamp-suite STAMP implementation
--
-- Copyright (c) 2026 Piotr "asmie" Olszewski
-- Licensed under MIT License
--
-- Enterprise OID: 1.3.6.1.4.1.65134 (IANA PEN 65134)
-- *****************************************************************

STAMP-SUITE-MIB DEFINITIONS ::= BEGIN

IMPORTS
    MODULE-IDENTITY, OBJECT-TYPE, Counter32, Counter64,
    Gauge32, Integer32, TimeTicks, Unsigned32
        FROM SNMPv2-SMI
    MODULE-COMPLIANCE, OBJECT-GROUP
        FROM SNMPv2-CONF
    TruthValue
        FROM SNMPv2-TC
    enterprises
        FROM SNMPv2-SMI;

stampSuiteMIB MODULE-IDENTITY
    LAST-UPDATED "202610030000Z"
    ORGANIZATION "stamp-suite project"
    CONTACT-INFO
        "https://github.com/asmie/stamp-suite"
    DESCRIPTION
        "MIB module for stamp-suite, an implementation of the
         Simple Two-Way Active Measurement Protocol (STAMP)
         per RFC 8762 and RFC 8972.

         All objects are read-only. The stamp-suite AgentX
         sub-agent (--snmp) serves them. A reflector process fills
         the reflector subtree; a sender process fills the sender
         subtree."
    REVISION     "202610030000Z"
    DESCRIPTION  "Object descriptions clarified to match the
                  implementation. No object was added or removed, and
                  no syntax, OID or access changed."
    REVISION     "202608050000Z"
    DESCRIPTION  "Version 1.0.0. Object definitions unchanged from the
                  initial version; re-stamped for the 1.0.0 release."
    REVISION     "202501010000Z"
    DESCRIPTION  "Initial version."
    ::= { enterprises 65134 }

-- ===================================================================
-- Top-level structure
-- ===================================================================

stampSuiteObjects     OBJECT IDENTIFIER ::= { stampSuiteMIB 1 }
stampSuiteConformance OBJECT IDENTIFIER ::= { stampSuiteMIB 2 }

-- ===================================================================
-- Reflector subtree
-- ===================================================================

stampReflector       OBJECT IDENTIFIER ::= { stampSuiteObjects 1 }
stampReflectorConfig OBJECT IDENTIFIER ::= { stampReflector 1 }
stampReflectorStats  OBJECT IDENTIFIER ::= { stampReflector 2 }

-- -------------------------------------------------------------------
-- Reflector Configuration
-- -------------------------------------------------------------------

stampReflAdminStatus OBJECT-TYPE
    SYNTAX      INTEGER { enabled(1), disabled(2) }
    MAX-ACCESS  read-only
    STATUS      current
    DESCRIPTION
        "Whether this process runs as a STAMP reflector.
         enabled(1) in reflector mode, disabled(2) in sender mode."
    ::= { stampReflectorConfig 1 }

stampReflListenAddr OBJECT-TYPE
    SYNTAX      OCTET STRING (SIZE (4|16))
    MAX-ACCESS  read-only
    STATUS      current
    DESCRIPTION
        "The configured local IP address (--local-addr) the
         reflector binds to. An all-zero value means all addresses.
         4 octets for IPv4, 16 octets for IPv6."
    ::= { stampReflectorConfig 2 }

stampReflListenPort OBJECT-TYPE
    SYNTAX      Unsigned32 (0..65535)
    MAX-ACCESS  read-only
    STATUS      current
    DESCRIPTION
        "The UDP port the reflector listens on (862 by default)."
    ::= { stampReflectorConfig 3 }

stampReflAuthMode OBJECT-TYPE
    SYNTAX      INTEGER { open(1), authenticated(2) }
    MAX-ACCESS  read-only
    STATUS      current
    DESCRIPTION
        "Authentication mode of the reflector per RFC 8762."
    ::= { stampReflectorConfig 4 }

stampReflTlvMode OBJECT-TYPE
    SYNTAX      INTEGER { echo(1), ignore(2) }
    MAX-ACCESS  read-only
    STATUS      current
    DESCRIPTION
        "TLV handling mode of the reflector (RFC 8972 Section 4).
         echo(1): process supported TLVs, echo them and set the
         U, M and I flags.
         ignore(2): copy everything after the base packet back
         unprocessed, as a reflector without TLV support does."
    ::= { stampReflectorConfig 5 }

stampReflStateful OBJECT-TYPE
    SYNTAX      TruthValue
    MAX-ACCESS  read-only
    STATUS      current
    DESCRIPTION
        "Whether stateful reflector mode is enabled (RFC 8762
         Section 4). When true, the reflector keeps an independent
         sequence counter for each session. A session is identified
         by both UDP endpoints, the SSID and the optional sender
         Micro-session ID."
    ::= { stampReflectorConfig 6 }

stampReflSessionTimeout OBJECT-TYPE
    SYNTAX      Unsigned32
    UNITS       "seconds"
    MAX-ACCESS  read-only
    STATUS      current
    DESCRIPTION
        "Session timeout in seconds. Sessions with no accepted
         packet for this long may be removed. 0 means no timeout."
    ::= { stampReflectorConfig 7 }

-- -------------------------------------------------------------------
-- Reflector Statistics
-- -------------------------------------------------------------------

stampReflPktsReceived OBJECT-TYPE
    SYNTAX      Counter64
    MAX-ACCESS  read-only
    STATUS      current
    DESCRIPTION
        "Total number of packets received by the reflector that
         passed the per-source rate limit, including packets that
         were dropped later for other reasons."
    ::= { stampReflectorStats 1 }

stampReflPktsReflected OBJECT-TYPE
    SYNTAX      Counter64
    MAX-ACCESS  read-only
    STATUS      current
    DESCRIPTION
        "Total number of reflected packets sent."
    ::= { stampReflectorStats 2 }

stampReflPktsDropped OBJECT-TYPE
    SYNTAX      Counter64
    MAX-ACCESS  read-only
    STATUS      current
    DESCRIPTION
        "Total number of received packets that were not answered,
         for any reason: parse or HMAC failures, rate limits,
         session limits, a full reply queue or cancelled replies."
    ::= { stampReflectorStats 3 }

stampReflActiveSessions OBJECT-TYPE
    SYNTAX      Gauge32
    MAX-ACCESS  read-only
    STATUS      current
    DESCRIPTION
        "Current number of sessions the reflector tracks."
    ::= { stampReflectorStats 4 }

stampReflUptime OBJECT-TYPE
    SYNTAX      TimeTicks
    MAX-ACCESS  read-only
    STATUS      current
    DESCRIPTION
        "Time since the process started, in hundredths of a second."
    ::= { stampReflectorStats 5 }

-- -------------------------------------------------------------------
-- Reflector Session Table
-- -------------------------------------------------------------------

stampReflSessionTable OBJECT-TYPE
    SYNTAX      SEQUENCE OF StampReflSessionEntry
    MAX-ACCESS  not-accessible
    STATUS      current
    DESCRIPTION
        "Table of the sessions the reflector tracks. Each row is
         one session, identified by both UDP endpoints, the SSID
         and the optional sender Micro-session ID. Several rows can
         share one sender address and port."
    ::= { stampReflector 3 }

stampReflSessionEntry OBJECT-TYPE
    SYNTAX      StampReflSessionEntry
    MAX-ACCESS  not-accessible
    STATUS      current
    DESCRIPTION
        "An entry representing a single reflector session."
    INDEX       { stampReflSessIndex }
    ::= { stampReflSessionTable 1 }

StampReflSessionEntry ::= SEQUENCE {
    stampReflSessIndex       Unsigned32,
    stampReflSessClientAddr  OCTET STRING,
    stampReflSessClientPort  Unsigned32,
    stampReflSessPktsRecv    Counter32,
    stampReflSessPktsXmit    Counter32,
    stampReflSessLastSeq     Unsigned32,
    stampReflSessLastActive  TimeTicks
}

stampReflSessIndex OBJECT-TYPE
    SYNTAX      Unsigned32
    MAX-ACCESS  not-accessible
    STATUS      current
    DESCRIPTION
        "Internal session ID, the same value as session_id in the
         control API. A session created again after expiry gets a
         new index."
    ::= { stampReflSessionEntry 1 }

stampReflSessClientAddr OBJECT-TYPE
    SYNTAX      OCTET STRING (SIZE (4|16))
    MAX-ACCESS  read-only
    STATUS      current
    DESCRIPTION
        "IP address of the STAMP sender for this session."
    ::= { stampReflSessionEntry 2 }

stampReflSessClientPort OBJECT-TYPE
    SYNTAX      Unsigned32 (0..65535)
    MAX-ACCESS  read-only
    STATUS      current
    DESCRIPTION
        "UDP source port of the STAMP sender for this session."
    ::= { stampReflSessionEntry 3 }

stampReflSessPktsRecv OBJECT-TYPE
    SYNTAX      Counter32
    MAX-ACCESS  read-only
    STATUS      current
    DESCRIPTION
        "Number of STAMP test packets received in this session."
    ::= { stampReflSessionEntry 4 }

stampReflSessPktsXmit OBJECT-TYPE
    SYNTAX      Counter32
    MAX-ACCESS  read-only
    STATUS      current
    DESCRIPTION
        "Number of STAMP test packets reflected in this session."
    ::= { stampReflSessionEntry 5 }

stampReflSessLastSeq OBJECT-TYPE
    SYNTAX      Unsigned32
    MAX-ACCESS  read-only
    STATUS      current
    DESCRIPTION
        "Sequence number of the last reflected packet in this session."
    ::= { stampReflSessionEntry 6 }

stampReflSessLastActive OBJECT-TYPE
    SYNTAX      TimeTicks
    MAX-ACCESS  read-only
    STATUS      current
    DESCRIPTION
        "Time since the last accepted packet in this session,
         in hundredths of a second."
    ::= { stampReflSessionEntry 7 }

-- ===================================================================
-- Sender subtree
-- ===================================================================

stampSender       OBJECT IDENTIFIER ::= { stampSuiteObjects 2 }
stampSenderConfig OBJECT IDENTIFIER ::= { stampSender 1 }
stampSenderStats  OBJECT IDENTIFIER ::= { stampSender 2 }

-- -------------------------------------------------------------------
-- Sender Configuration
-- -------------------------------------------------------------------

stampSendRemoteAddr OBJECT-TYPE
    SYNTAX      OCTET STRING (SIZE (4|16))
    MAX-ACCESS  read-only
    STATUS      current
    DESCRIPTION
        "Reflector IP address of the sender. When several
         reflectors are configured, the first one."
    ::= { stampSenderConfig 1 }

stampSendRemotePort OBJECT-TYPE
    SYNTAX      Unsigned32 (0..65535)
    MAX-ACCESS  read-only
    STATUS      current
    DESCRIPTION
        "Reflector UDP port of the sender (862 by default)."
    ::= { stampSenderConfig 2 }

stampSendLocalPort OBJECT-TYPE
    SYNTAX      Unsigned32 (0..65535)
    MAX-ACCESS  read-only
    STATUS      current
    DESCRIPTION
        "Configured local UDP port of the sender. 0 means the
         sender uses a randomized dynamic port."
    ::= { stampSenderConfig 3 }

stampSendPktCount OBJECT-TYPE
    SYNTAX      Unsigned32
    MAX-ACCESS  read-only
    STATUS      current
    DESCRIPTION
        "Configured number of test packets to send to each
         reflector. 0 means send until the configured duration
         ends or the sender is stopped."
    ::= { stampSenderConfig 4 }

stampSendDelay OBJECT-TYPE
    SYNTAX      Unsigned32
    UNITS       "milliseconds"
    MAX-ACCESS  read-only
    STATUS      current
    DESCRIPTION
        "Configured interval between test packets, in whole
         milliseconds (rounded down, so intervals below 1 ms read
         as 0). With a Poisson schedule this is the mean interval."
    ::= { stampSenderConfig 5 }

stampSendAuthMode OBJECT-TYPE
    SYNTAX      INTEGER { open(1), authenticated(2) }
    MAX-ACCESS  read-only
    STATUS      current
    DESCRIPTION
        "Authentication mode of the sender per RFC 8762."
    ::= { stampSenderConfig 6 }

-- -------------------------------------------------------------------
-- Sender Statistics
-- -------------------------------------------------------------------

stampSendPktsSent OBJECT-TYPE
    SYNTAX      Counter32
    MAX-ACCESS  read-only
    STATUS      current
    DESCRIPTION
        "Total number of test packets sent, summed over all
         reflectors."
    ::= { stampSenderStats 1 }

stampSendPktsRecv OBJECT-TYPE
    SYNTAX      Counter32
    MAX-ACCESS  read-only
    STATUS      current
    DESCRIPTION
        "Total number of test packets answered by a reflected
         packet, summed over all reflectors."
    ::= { stampSenderStats 2 }

stampSendPktsLost OBJECT-TYPE
    SYNTAX      Counter32
    MAX-ACCESS  read-only
    STATUS      current
    DESCRIPTION
        "Total number of test packets with no reply within the
         timeout, summed over all reflectors."
    ::= { stampSenderStats 3 }

stampSendRttMin OBJECT-TYPE
    SYNTAX      Gauge32
    UNITS       "microseconds"
    MAX-ACCESS  read-only
    STATUS      current
    DESCRIPTION
        "Minimum round-trip time in microseconds, over all
         reflectors."
    ::= { stampSenderStats 4 }

stampSendRttMax OBJECT-TYPE
    SYNTAX      Gauge32
    UNITS       "microseconds"
    MAX-ACCESS  read-only
    STATUS      current
    DESCRIPTION
        "Maximum round-trip time in microseconds, over all
         reflectors."
    ::= { stampSenderStats 5 }

stampSendRttAvg OBJECT-TYPE
    SYNTAX      Gauge32
    UNITS       "microseconds"
    MAX-ACCESS  read-only
    STATUS      current
    DESCRIPTION
        "Mean round-trip time in microseconds, over all
         reflectors."
    ::= { stampSenderStats 6 }

stampSendJitter OBJECT-TYPE
    SYNTAX      Gauge32
    UNITS       "microseconds"
    MAX-ACCESS  read-only
    STATUS      current
    DESCRIPTION
        "Smoothed jitter in microseconds: the RFC 3550 interarrival
         jitter estimator, J = J + (|D| - J)/16, applied to the
         difference D between consecutive round-trip times."
    ::= { stampSenderStats 7 }

stampSendLossPct OBJECT-TYPE
    SYNTAX      Gauge32
    MAX-ACCESS  read-only
    STATUS      current
    DESCRIPTION
        "Lost test packets as a percentage of test packets sent,
         multiplied by 100. For example, 250 represents 2.50% loss."
    ::= { stampSenderStats 8 }

-- ===================================================================
-- Conformance
-- ===================================================================

stampSuiteCompliances OBJECT IDENTIFIER ::= { stampSuiteConformance 1 }
stampSuiteGroups      OBJECT IDENTIFIER ::= { stampSuiteConformance 2 }

stampSuiteFullCompliance MODULE-COMPLIANCE
    STATUS      current
    DESCRIPTION
        "Full compliance with the STAMP-SUITE-MIB."
    MODULE
        MANDATORY-GROUPS {
            stampReflectorConfigGroup,
            stampReflectorStatsGroup,
            stampReflectorSessionGroup,
            stampSenderConfigGroup,
            stampSenderStatsGroup
        }
    ::= { stampSuiteCompliances 1 }

stampReflectorConfigGroup OBJECT-GROUP
    OBJECTS {
        stampReflAdminStatus,
        stampReflListenAddr,
        stampReflListenPort,
        stampReflAuthMode,
        stampReflTlvMode,
        stampReflStateful,
        stampReflSessionTimeout
    }
    STATUS      current
    DESCRIPTION
        "Reflector configuration objects."
    ::= { stampSuiteGroups 1 }

stampReflectorStatsGroup OBJECT-GROUP
    OBJECTS {
        stampReflPktsReceived,
        stampReflPktsReflected,
        stampReflPktsDropped,
        stampReflActiveSessions,
        stampReflUptime
    }
    STATUS      current
    DESCRIPTION
        "Reflector statistics objects."
    ::= { stampSuiteGroups 2 }

stampReflectorSessionGroup OBJECT-GROUP
    OBJECTS {
        stampReflSessClientAddr,
        stampReflSessClientPort,
        stampReflSessPktsRecv,
        stampReflSessPktsXmit,
        stampReflSessLastSeq,
        stampReflSessLastActive
    }
    STATUS      current
    DESCRIPTION
        "Reflector session table objects."
    ::= { stampSuiteGroups 3 }

stampSenderConfigGroup OBJECT-GROUP
    OBJECTS {
        stampSendRemoteAddr,
        stampSendRemotePort,
        stampSendLocalPort,
        stampSendPktCount,
        stampSendDelay,
        stampSendAuthMode
    }
    STATUS      current
    DESCRIPTION
        "Sender configuration objects."
    ::= { stampSuiteGroups 4 }

stampSenderStatsGroup OBJECT-GROUP
    OBJECTS {
        stampSendPktsSent,
        stampSendPktsRecv,
        stampSendPktsLost,
        stampSendRttMin,
        stampSendRttMax,
        stampSendRttAvg,
        stampSendJitter,
        stampSendLossPct
    }
    STATUS      current
    DESCRIPTION
        "Sender statistics objects."
    ::= { stampSuiteGroups 5 }

END
